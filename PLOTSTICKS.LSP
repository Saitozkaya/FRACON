;***********************************************************
;PLOTSTICKS.LSP
;************************************************************
;program to display fractures generated by bal.c program
;programmer sait Ismail Ozkaya
;Platform: ACAD 
;The data file for this program must look like
;  x1           y1         x2          y2        colorcode-sets (1-fault related)
;3174504.500 970199.312 3174495.500 970200.688     3
;3174499.750 970198.875 3174500.250 970201.125     4
;3174501.750 970599.312 3174498.250 970600.688     3
;3174499.750 970599.562 3174500.250 970600.438     4
;3174518.750 970999.812 3174481.250 971000.188     3
;3174500.000 970995.312 3174500.000 971004.688     4
;3174498.750 971399.250 3174501.250 971400.750     3
;3174499.750 971400.312 3174500.250 971399.688     4
;3174498.250 971798.625 3174501.750 971801.375     3
;3174499.750 971800.438 3174500.250 971799.562     4
;......
;endfile
;**********************************************************
;The following input file must be prepared
;**********************************************************
;corimgfc.prn
;1000
;3172000
;965000
;3190000
;985000
;1
;0.1
;2000
;
;rows
;1  data file name
;2  scale
;3  xorigin
;4  yorigin
;5  xrite
;6  yup
;7  color option >0 each contour has a different color
;8  text size for plotting contour values
;9  width between utm lines
;
;***********************************************************
 (defun plotsticks ( / &xg &numberlist &err &mazgal
    &linecnt &mashfile &nline  &xor &yor &scale &artmalik 
    &infile &coloropt)
 ;**********************************************************
 ;*********************************************************
  (Defun *error* (msg)
 ;*******************************************************
 ;***AutoCAD error routine...
 ;*********************************************************
    (terpri)
    (princ msg)
    (princ)
   );end error..
 ;*******************************************************
 (defun READIT ( / ilk n i mi ilkflag ilkebay)
 ;*******************************************************
 ;***Procedure to read a line from input text file..
 ;*******************************************************
 ;+++++++++++++++++++++++++++++++++++++++++++++++
  (defun elimbl (  /  ie ne ilke)
 ;+++++++++++++++++++++++++++++++++++++++++++++++
 ;***Subprocedure to eliminate blanks..
 ;+++++++++++++++++++++++++++++++++++++++++++++++
   (setq ilkebay -10)
   (if (/= &xg nil)
    (progn
     (setq
       ie 1
       ne (strlen &xg)
     );end setq..
     (while (and (<= ie ne) (< ilkebay 0))
      (setq
       ilke (substr &xg ie 1)
      );end setq
      (if (/= ilke " ")
       (setq
        &xg (substr &xg ie)
        ilkebay 10
       );end setq..
      );end if..
      (setq ie (1+ ie))
     );end while..
    );end progn..
   );end if..
   (if (< ilkebay 0)
    (setq
      &linecnt (1+ &linecnt)
    );end setq..
   );end if..
 
   (if (> &linecnt &nline)
    (progn
      (terpri)
      (princ "Unexpected end of file or no endfile mark..")
      (setq &err (/ 1 nil))
    );end progn
  );end if..
 );end elimbl..
 ;+++++++++++++++++++++++++++++++++
  (setq
   &xg (read-line &mashfile)
  );end setq..
 
  (elimbl)
 
  (if (> ilkebay 0)
   (setq
    ilk (substr &xg 1 1)
   );end setq..
   ;else
    (setq ilk "#")
  );end if..
  (while  (= ilk "#")
   (setq
    &xg (read-line &mashfile)
   );end setq..
   (elimbl)
   (if (> ilkebay 0)
    (setq
     ilk (substr &xg 1 1)
    );end setq..
   ;else
    (setq ilk "#")
   );end if..
  );end while..
    (setq
      n (strlen &xg)
      i n
      ilkflag -10
      mi n
    );end setq
    (while ( and (> i 0) (< ilkflag 0))
       (setq
         ilk (substr &xg i 1)
      );end setq..
      (if (/= ilk " ")
        (setq
          ilkflag 10
          mi i
        );end setq..
       );end if..
       (setq
         i (1- i)
      );end setq..
    ); end while..
    (setq &xg (substr &xg 1 mi))
    (setq &xg (strcase &xg T))
 );end readit..
 ;*******************************************************
 (defun PROCURE ( /  ip np alfa number harf)
 ;*******************************************************
 ;***Procedure to parse input text line and extract
 ;number fields. &numberlist is the list of numbers...
 ;*******************************************************
  (setq
    &numberlist nil
    ip 1
    np (strlen &xg)
    alfa " "
    number nil
    harf (substr &xg 1 1)
  );end setq..
  (while (<= ip np)
   (while ( and (<= ip np) (= harf " "))
     (setq
       ip (1+ ip)
       harf (substr &xg ip 1)
      );end setq..
   );end while..
   (if (<= ip np)
   (progn
    (while (and (<= ip np)
               (/= harf " ")
               (/= harf ",")
          );end and..
     (setq
     sayi (ascii harf)
     );end setq..
     (if ( and (/= sayi 45) (/= sayi 46))
      (if (or (< sayi 48) (> sayi 57))
       (progn
        (terpri)
        (princ "Warning - Non-numeric character...")
        (terpri)
       );end progn..
      );end if..
     );end if (/= sayi 45)
     (setq
      alfa (strcat alfa harf)
      ip (1+ ip)
      harf (substr &xg ip 1)
     );end setq..
    ); end while..
    (setq
     number (atof alfa)
     alfa " "
     &numberlist (cons number &numberlist)
     ip (1+ ip)
     harf (substr &xg ip 1)
    );end setq..
   );end progn..
   );end if..
  );end while (<= ip np..
  (if (/= &numberlist nil)
   (progn
   (setq &numberlist (reverse &numberlist))
   );end progn..
  );end if..
 );end procure..
 
 ;******************************************************
 (defun OKUCOR (   /  x1 y1 p1 x2 y2 p2  aci cp1 cp2 cp3 cp4
  yaci renk)
 ;******************************************************
 ;Procedure to read coordinates of joints of the network
 ;******************************************************
 (setq
   &linecnt 0
   piov2 1.57079
   renk 1
   &mashfile (open  &infile  "r")
 );end setq..
  (readit)
 (while  (/= &xg "endfile")
   (procure)
    (setq
     x1 (nth 0 &numberlist)
     x1 ( / (- x1 &xor) &scale)
     y1 (nth 1 &numberlist)
     y1 ( / (- y1 &yor) &scale)
     p1 (list x1 y1)
     x2 (nth 2 &numberlist)
     x2 ( / (- x2 &xor) &scale)
     y2 (nth 3 &numberlist)
     y2 ( / (- y2 &yor) &scale)
     p2 (list x2 y2) 
     renk (nth 4 &numberlist) 
     renk (fix renk)   
    );end setq..
  
     (if (> &coloropt 0)
      (command "color" renk)
     ;else
       (command "color" 7)
     ); end if..
   
     (command "line" p1 p2 "")
    
   (readit)
  );end while..
  (close &mashfile)
  );end okucor..

;**********************************************************
(defun OKUINP ( / )
    
  (setq &infile "plotsticks.inp")

   
  (setq &mashfile (open &infile "r"))

  (readit)
  (setq &infile &xg)
   
  (readit)
  (procure)

   (PRINT &INFILE)

  (setq &scale (nth 0 &numberlist))
   
  (readit)
  (procure)
  (setq &xor (nth 0 &numberlist))
 
  (readit)
  (procure)
  (setq &yor (nth 0 &numberlist)) 
  (readit)
   
  (procure)
  (setq &xrt (nth 0 &numberlist)) 
  
  (readit)
  (procure)
  (setq &yup (nth 0 &numberlist)) 
 
  (readit)
  (procure)
  (setq &coloropt (nth 0 &numberlist))
  (setq &coloropt (fix &coloropt))
 
  (readit)
  (procure)
  (setq &artmalik (nth 0 &numberlist))
   
  (readit)
  (procure)
  (setq &mazgal (nth 0 &numberlist))
 
  


  (close &mashfile)
 ); end okuinp

;*********************************************************
(defun DRAWFRAME ( / xr yu p1p2 p3 xpos yup ydown utm  ypos
 xleft xrite ptext ptx pty )

;Draw a frame around the contour map using the ll lr lu ru
;points scale and coordinates of the origin (l

  
 (setq 
   xr  (/ (- &xrt &xor) &scale)
   yu  (/ (- &yup &yor) &scale)
 );end setq..

 (command "color" 7)

 (setq
  ydown 0
  xpos 0
  yups (/ (- &yup &yor) &scale)
  utm &xor
  p1 (list xr ydown)
  p2 (list xr yups)

 );
 

(command "line" p1 p2 "")

 (setq 
   p1 (list xpos yups)
   p2 (list xr yups)
 ); end setq..

 (command "line" p1 p2 "")
 
 (setq 
   p1 (list xpos ydown)
   p2 (list xpos yups)
  ); end setq..


(command "line" p1 p2 "")

 (setq
 
  p1 (list xpos ydown)
  p2 (list xr ydown)

 );
 

(command "line" p1 p2 "")


 (setq
   ptx  xpos
   pty (- ydown
(* 2 &artmalik))
   ptext (list ptx pty)
  );end setq..
 
 (command "text"  ptext  &artmalik  "0" (rtos &xor 2 0) )

 (setq
   ptx  (- xpos (* 2 &artmalik))
   pty  ydown 
   ptext (list ptx pty)
  );end setq..

 (command "text"  ptext  &artmalik  "90" (rtos &yor 2 0) )

(setq
    xpos (+ xpos (/ &mazgal &scale))
    utm (+ utm &mazgal)

  );end setq..

 (while (<= xpos xr)
  (setq
     p1 (list xpos  ydown)
     p2 (list xpos  yups)
  );end setq..
  (command "line" p1 p2 "")

  
  (setq
     pty (- ydown (* 2 &artmalik))
     ptx xpos
     ptext (list ptx pty)
     
  );end setq..


  (command "text" "j" "c"  ptext  &artmalik  "0" (rtos utm 2 0) )

  

  (setq
    xpos (+ xpos (/ &mazgal &scale))
    utm (+ utm &mazgal)

  );end setq..

 ); end while..


 (setq
  xleft 0
  xrite (/ (- &xrt &xor) &scale)
  ypos 0
  utm &yor
 );

 (setq
    ypos (+ ypos (/ &mazgal &scale))
    utm (+ utm &mazgal)
  );end setq..

 (while (<= ypos yu)
  (setq
     p1 (list xleft ypos )
     p2 (list xrite ypos)
  );end setq..

  (command "line" p1 p2 "")

  (setq
     ptx (- xleft (* 2 &artmalik))
     pty ypos
     ptext (list ptx pty)
     
  );end setq..

  (command "text"  "j" "c" ptext  &artmalik  "90" (rtos utm 2 0) )

  (setq
    ypos (+ ypos (/ &mazgal &scale))
    utm (+ utm &mazgal)
  );end setq..
 ); end while..

);end drawframe
;***********************************************************
  (setvar "cmdecho" 0)
  (setq &nline 1000)
  (terpri)
  (okuinp)
  (setq cfile (findfile  &infile))
   (if (= cfile nil)
    (progn
     (terpri)
     (print "No file..")
     (princ)
     (setq &err (/ 1 0))
   );end progn
  );end if
   
   (drawframe)
   (okucor)
   (command "redraw")
 );end plotsticks
